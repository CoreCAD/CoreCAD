# Cruth dev launch helper (used by `pixi run freecad-test`).
#
# freecad-test launches with a throwaway --user-cfg that is wiped each run, so the
# saved window layout starts empty and the Model and Report view panels come up
# toggled OFF in this build. This macro re-enables them at startup.
#
# It only changes runtime dock visibility (Qt keeps the View > Panels menu items in
# sync), and writes nothing to user.cfg — so the pristine-defaults guarantee that
# freecad-test exists to provide is preserved.
import FreeCADGui as Gui
from PySide import QtCore, QtWidgets

_PANELS = ("Model", "Report view")


def _show_panels():
    mw = Gui.getMainWindow()
    if mw is None:
        return
    for dock in mw.findChildren(QtWidgets.QDockWidget):
        if dock.objectName() in _PANELS:
            dock.setVisible(True)


# Workbench activation / the Start page / the ribbon settling can re-hide the docks
# *after* a single deferred call runs (observed still-hidden at ~2.5s). Re-assert across a
# longer window so the panels stay up regardless of when the last re-hide lands.
for _ms in (1500, 3000, 5000, 8000):
    QtCore.QTimer.singleShot(_ms, _show_panels)
